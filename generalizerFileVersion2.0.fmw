FME workspace generalizerFileVersion2.0.fmw

Parameters:
- lastsketchsegment = 2   # Enter Numeric Data 2
- RouteSeq = 0,3   # Enter Text Data 2
- SketchRouteSeq = 0,2   # Enter Text Data 3
- Alignment = {"sketchMap1.jpg":{"1":{"BaseAlign":{"0":[11,9,10]},"SketchAlign":{"0":["S7"]},"genType":"Amalgamation","degreeOfGeneralization":0.6666666666666666},"2":{"BaseAlign":{"0":[0]},"SketchAlign":{"0":["S0"]},"genType":"No generalization","degreeOfGeneralization":0},"3":{"BaseAlign":{"0":[2]},"SketchAlign":{"0":["S1"]},"genType":"No generalization","degreeOfGeneralization":0},"4":{"BaseAlign":{"0":[3]},"SketchAlign":{"0":["S2"]},"genType":"No generalization","degreeOfGeneralization":0},"5":{"BaseAlign":{"0":[4]},"SketchAlign":{"0":["S3"]},"genType":"No generalization","degreeOfGeneralization":0},"6":{"BaseAlign":{"0":[5]},"SketchAlign":{"0":["S4"]},"genType":"No generalization","degreeOfGeneralization":0},"7":{"BaseAlign":{"0":[7]},"SketchAlign":{"0":["S5"]},"genType":"No generalization","degreeOfGeneralization":0},"8":{"BaseAlign":{"0":[8]},"SketchAlign":{"0":["S6"]},"genType":"No generalization","degreeOfGeneralization":0},"id":8,"checkAlignnum":9}}   # Enter Text Data
- DestDataset_GEOJSON = generalizedmap   # Destination GeoJSON File
- lastsegment = 3   # Enter Numeric Data
- SourceDataset_GEOJSON_4 = $(FME_MF_DIR)Sketchmap_generalize\generalizedMap\inputsketchMap.json   # Source GeoJSON File or URL
- SourceDataset_GEOJSON = $(FME_MF_DIR)Sketchmap_generalize\generalizedMap\inputbaseMap.json   # Source GeoJSON File or URL

Readers:
- GEOJSON_2: GEOJSON from $(SourceDataset_GEOJSON)
- GEOJSON_3: GEOJSON from $(SourceDataset_GEOJSON_4)

Writers:
- GEOJSON_1: GEOJSON to $(DestDataset_GEOJSON)

Note: Creator_3 [Creator] / General: / Geometry Source: Geometry Object / Geometry Object: Null / Coordinate System: <not set> / Number to Create: 1 / Create At End: No / Output Attribute Name: / Creation Instance: _creation_instance
Creator_3
    GEOMTYPE = Geometry Object
    NUM = 1
    CREATED -> AttributeCreator_3
Note: AttributeCreator_3 [AttributeCreator] / Attributes To Create: New AttributeAttribute Valuejson$(Alignment)
AttributeCreator_3
    ATTR_TABLE = SET_TO json = $(Alignment)
    -> Logger_3
Logger_3
    LOG_FEATURE = LOG_ONLY
    MAXCOORDS = 20
    MAXFEATS = 20
    MESSAGE = Feature is:
    SEVERITY = INFO
    LOGGED -> JSONFragmenter_3
Note: JSONFragmenter_3 [JSONFragmenter] / Source: / Input Source: JSON Attribute / JSON Attribute: json / General: / JSON Query: json[*][*] / Fragment as Format: JSON / Reject Features which Produce No Fragments: No / Flattening: / Flatten Query Result into Attributes: Yes / Recursively Flatten Objects/Arrays: No / Prefix New Attributes With: <not set> / Attributes to Expose: BaseAlign SketchAlign genType
Note: JSONFragmenter
JSONFragmenter_3
    EXPLODE_FORMAT = JSON
    EXTRACT_ATTR = Yes
    JSON_ATTR = json
    JSON_QUERY = json[*][*]
    NEW_ATTRIBUTES = BaseAlign SketchAlign genType
    READ_FROM_FILE = NO
    RECURSIVE = No
    REJECT_EMPTY_LISTS = NO
    FRAGMENTS -> Logger_5
Logger_5
    LOG_FEATURE = LOG_ONLY
    MAXCOORDS = 20
    MAXFEATS = 20
    MESSAGE = Feature is:
    SEVERITY = INFO
    LOGGED -> JSONFlattener_3
JSONFlattener_3
    ERROR_LIST_ATTR = _json_error
    JSON_DOCUMENT = @Value(json)
    READ_FROM_FILE = NO
    RECURSIVE = Yes
    -> Logger_4
Logger_4
    LOG_FEATURE = LOG_ONLY
    MAXCOORDS = 20
    MAXFEATS = 20
    MESSAGE = Feature is:
    SEVERITY = INFO
    LOGGED -> JSONExtractor
JSONExtractor
    EXTRACT_QUERY_TABLE = listofbaseID json[*]
    JSON_DOCUMENT = @Value(BaseAlign)
    READ_FROM_FILE = NO
    EVALUATED -> StringReplacer
StringReplacer
    CASE = NO
    FIND_TEXT = [
    NO_MATCH = _FME_NO_OP_
    REGEXP = NO
    REPLACE_TEXT = " "
    SRC_ATTRS = listofbaseID
    -> StringReplacer_2
StringReplacer_2
    CASE = NO
    FIND_TEXT = ]
    NO_MATCH = _FME_NO_OP_
    REGEXP = NO
    SRC_ATTRS = listofbaseID
    -> AttributeSplitter
AttributeSplitter
    ATTR_NAME = listofbaseID
    DELIMITER = ,
    DROP_EMPTY_PARTS = No
    LIST_NAME = Baselist
    TRIM_OPTION = Both
    -> AttributeFilter
AttributeFilter
    ATTR_NAME = genType
    ATTR_VALUES = <Empty>,<Missing>,<Null>,<Unfiltered>,No generalization,Amalgamation,OmissionMerge,Collapse
    No generalization -> Non_generalized [REQUESTOR]
    Amalgamation -> Amalgamate [REQUESTOR]
    OmissionMerge -> OmissionMerge [REQUESTOR]
    Collapse -> Collapse [REQUESTOR]
Creator_5
    GEOMTYPE = Geometry Object
    NUM = 1
    CREATED -> AttributeCreator_5
AttributeCreator_5
    ATTR_TABLE = SET_TO json = $(SketchRouteSeq)
    -> StringReplacer_5
StringReplacer_5
    CASE = NO
    FIND_TEXT = [
    NO_MATCH = _FME_NO_OP_
    REGEXP = NO
    SRC_ATTRS = json
    -> StringReplacer_6
StringReplacer_6
    CASE = NO
    FIND_TEXT = ]
    NO_MATCH = _FME_NO_OP_
    REGEXP = NO
    SRC_ATTRS = json
    -> AttributeSplitter_3
AttributeSplitter_3
    ATTR_NAME = json
    DELIMITER = ,
    DROP_EMPTY_PARTS = No
    LIST_NAME = routeseq
    TRIM_OPTION = Both
    -> RouteSeparator_2 [REQUESTOR]
inputbaseMap (reader GEOJSON_2)
    attributes: id int, isRoute string, feat_type string, selected boolean, aligned boolean, otype string, missing boolean
    -> StringFormatter
StringFormatter
    FORMAT = d
    SRC_ATTRS = id
    -> OmissionMerge [SUPPLIER]
    -> Amalgamate [SUPPLIER]
    -> Collapse [SUPPLIER]
    -> Non_generalized [SUPPLIER]
Non_generalized: ListBasedFeatureMerger
    ATTR_ACCUM_MODE = Merge Supplier
    ATTR_CONFLICT_RES = Use Requestor
    BUILD_INCOMPLETE = Merge Supplier Information
    GEOM_TYPE = Build Polygons
    IGNORE_NULLS = No
    MERGE_TYPE = Attributes and Geometry
    MODE = AUTO
    PROCESS_DUPS = Yes
    REFEEATTR = @Value(id)
    REFERATTR = Baselist{}
    MERGED -> RouteSeparator [SUPPLIER]
    UNUSED_SUPPLIER -> RouteSeparator [SUPPLIER]
OmissionMerge: ListBasedFeatureMerger
    ATTR_ACCUM_MODE = Merge Supplier
    ATTR_CONFLICT_RES = Use Requestor
    BUILD_INCOMPLETE = Merge Supplier Information
    GEOM_TYPE = Build Polygons
    IGNORE_NULLS = No
    MERGE_TYPE = Attributes and Geometry
    MODE = AUTO
    PROCESS_DUPS = Yes
    REFEEATTR = @Value(id)
    REFERATTR = Baselist{}
    MERGED -> LineCombiner
LineCombiner
    ACCUM_ATTRS_NAME = Merge Incoming Attributes
    BREAK = no
    BREAK_CONNECTION_ATTRIBUTES = id
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    LIST_ATTRS_TO_INCLUDE = id
    LIST_NAME = OMID
    PRESERVE = no
    TOPOLOGY = End noded
    LINE -> RouteSeparator [SUPPLIER]
Amalgamate: ListBasedFeatureMerger
    ATTR_ACCUM_MODE = Merge Supplier
    ATTR_CONFLICT_RES = Use Requestor
    BUILD_INCOMPLETE = Merge Supplier Information
    GEOM_TYPE = Build Polygons
    IGNORE_NULLS = No
    MERGE_TYPE = Attributes and Geometry
    MODE = AUTO
    PROCESS_DUPS = Yes
    REFEEATTR = @Value(id)
    REFERATTR = Baselist{}
    MERGED -> HullAccumulator
HullAccumulator
    3DMODE_PARAM = 2D
    ACCUM_INPUT_ATTRS = Merge Incoming Attributes
    GROUP_BY = id
    HULLTYPE_PARAM = Convex ()
    HULL -> RouteSeparator [SUPPLIER]
Collapse: ListBasedFeatureMerger
    ATTR_ACCUM_MODE = Merge Supplier
    ATTR_CONFLICT_RES = Use Requestor
    BUILD_INCOMPLETE = Merge Supplier Information
    GEOM_TYPE = Build Polygons
    IGNORE_NULLS = No
    MERGE_TYPE = Attributes and Geometry
    MODE = AUTO
    PROCESS_DUPS = Yes
    REFEEATTR = @Value(id)
    REFERATTR = Baselist{}
    MERGED -> CenterPointReplacer
CenterPointReplacer
    POINTTYPE = CENTEROFGRAV
    POINT -> Bufferer
Bufferer
    ANGLE = 22.5
    CAP_STYLE = Square
    CORNER_STYLE = Arc
    MODE = AREA
    OFFSET = 1
    OFFSET_UNITS = NONE
    PRECISION = APPROX
    BUFFERED -> RouteSeparator [SUPPLIER]
inputsketchMap (reader GEOJSON_3)
    attributes: id int, sid string, isRoute string, mapType string, feat_type string, selected boolean, aligned boolean, otype string
    -> RouteSeparator_2 [SUPPLIER]
RouteSeparator_2: ListBasedFeatureMerger
    ATTR_ACCUM_MODE = Merge Supplier
    ATTR_CONFLICT_RES = Use Requestor
    BUILD_INCOMPLETE = Merge Supplier Information
    IGNORE_NULLS = No
    MERGE_TYPE = Attributes Only
    MODE = AUTO
    PROCESS_DUPS = Yes
    REFEEATTR = @Value(id)
    REFERATTR = routeseq{}
    USED_SUPPLIER -> LineCombiner_3
    USED_SUPPLIER -> NetworkFlowOrientor_2 [LINE]
    USED_SUPPLIER -> StringSearcher_2
    UNUSED_SUPPLIER -> FeatureJoiner_3 [LEFT]
StringSearcher_2
    CASE = no
    MATCHED_RESULT_ATTR = _first_match
    REGEXP = $(lastsketchsegment)
    STRING_TO_SEARCH = @Value(id)
    MATCHED -> Extract_End_Points_3 [Input_Features]
Extract_End_Points_3: Extract End Points
    Buffer = 0
    BufferUnit = Feet
    ExtractGeometry = Yes
    Point_Output -> FeatureMerger_3 [REQUESTOR]
LineCombiner_3
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Extract_End_Points_4 [Input_Features]
Extract_End_Points_4: Extract End Points
    Buffer = 0
    BufferUnit = Feet
    ExtractGeometry = Yes
    Point_Output -> FeatureMerger_3 [SUPPLIER]
FeatureMerger_3
    ATTR_ACCUM_MODE = Merge Supplier
    ATTR_CONFLICT_RES = Use Requestor
    IGNORE_NULLS = No
    JOIN_KEYS = @Value(point_x) @Value(point_x) AUTO @Value(point_y) @Value(point_y) AUTO
    MERGE_TYPE = Attributes Only
    PROCESS_DUPS = NO
    REJECT_NULL_MISSING_KEYS = No
    SUPPLIERS_FIRST = No
    USED_SUPPLIER -> NetworkFlowOrientor_2 [DESTINATION]
NetworkFlowOrientor_2
    DIRECTION_ATTR = _direction
    NETWORK -> FeatureJoiner_3 [RIGHT]
FeatureJoiner_3
    ATTR_CONFLICT_RES = Prefer Left
    GEOMETRY_HANDLING = Aggregate Left and Right (Enforce Unique Names)
    JOIN_KEYS = id id AUTO
    JOIN_MODE = Full
    JOINED -> GeometryExtractor_2
GeometryExtractor_2
    ATTR = _geometry
    JSON_MAX_DIGITS = 7
    KIND_LONG = GeoJSON
    REMOVE_GEOMETRY = No
    -> AttributeExposer
AttributeExposer
    ATTR_LIST = fme_type
    -> Tester
Tester
    BOOL_OP = OR
    TEST_CLAUSE = TEST @Value(fme_type) = fme_point
    TEST_MODE = TEST
    PASSED -> Bufferer_2
    FAILED -> sf (writer GEOJSON_1)
    FAILED -> ListBasedFeatureMerger [SUPPLIER]
    FAILED -> LineOnLineOverlayer_3 [LINE]
Bufferer_2
    ANGLE = 22.5
    CAP_STYLE = Square
    CORNER_STYLE = Arc
    MODE = AREA
    OFFSET = 1
    OFFSET_UNITS = NONE
    PRECISION = APPROX
    BUFFERED -> sf (writer GEOJSON_1)
LineOnLineOverlayer_3
    ATTRS_ACCUM_MODE = Merge Attributes
    CLEANING_TOLERANCE = Automatic
    DEAGGREGATE_INPUT = Yes
    GENERATE_LIST_DROP = NO
    OV_ATTR = _overlaps
    SEPARATE_COLLINEAR_SEGMENTS = No
Creator_4
    GEOMTYPE = Geometry Object
    NUM = 1
    CREATED -> AttributeCreator_4
AttributeCreator_4
    ATTR_TABLE = SET_TO json = $(RouteSeq)
    -> StringReplacer_3
StringReplacer_3
    CASE = NO
    FIND_TEXT = [
    NO_MATCH = _FME_NO_OP_
    REGEXP = NO
    SRC_ATTRS = json
    -> StringReplacer_4
StringReplacer_4
    CASE = NO
    FIND_TEXT = ]
    NO_MATCH = _FME_NO_OP_
    REGEXP = NO
    SRC_ATTRS = json
    -> AttributeSplitter_2
AttributeSplitter_2
    ATTR_NAME = json
    DELIMITER = ,
    DROP_EMPTY_PARTS = No
    LIST_NAME = routeseq
    TRIM_OPTION = Both
    -> RouteSeparator [REQUESTOR]
RouteSeparator: ListBasedFeatureMerger
    ATTR_ACCUM_MODE = Merge Supplier
    ATTR_CONFLICT_RES = Use Requestor
    BUILD_INCOMPLETE = Merge Supplier Information
    IGNORE_NULLS = No
    MERGE_TYPE = Attributes Only
    MODE = AUTO
    PROCESS_DUPS = Yes
    REFEEATTR = @Value(id)
    REFERATTR = routeseq{}
    USED_SUPPLIER -> LineCombiner_2
    USED_SUPPLIER -> NetworkFlowOrientor [LINE]
    USED_SUPPLIER -> StringSearcher
    USED_SUPPLIER -> AttributeFilter_2
    UNUSED_SUPPLIER -> AttributeFilter_3
    UNUSED_SUPPLIER -> AttributeFilter_2
    <REJECTED> -> FeatureJoiner_2 [LEFT]
StringSearcher
    CASE = no
    MATCHED_RESULT_ATTR = _first_match
    REGEXP = $(lastsegment)
    STRING_TO_SEARCH = @Value(listofbaseID)
    MATCHED -> Extract_End_Points [Input_Features]
Extract_End_Points: Extract End Points
    Buffer = 0
    BufferUnit = Feet
    ExtractGeometry = Yes
    Point_Output -> FeatureMerger_2 [REQUESTOR]
LineCombiner_2
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Extract_End_Points_2 [Input_Features]
Extract_End_Points_2: Extract End Points
    Buffer = 0
    BufferUnit = Feet
    ExtractGeometry = Yes
    Point_Output -> FeatureMerger_2 [SUPPLIER]
FeatureMerger_2
    ATTR_ACCUM_MODE = Merge Supplier
    ATTR_CONFLICT_RES = Use Requestor
    IGNORE_NULLS = No
    JOIN_KEYS = @Value(point_x) @Value(point_x) AUTO @Value(point_y) @Value(point_y) AUTO
    MERGE_TYPE = Attributes Only
    PROCESS_DUPS = NO
    REJECT_NULL_MISSING_KEYS = No
    SUPPLIERS_FIRST = No
    USED_SUPPLIER -> NetworkFlowOrientor [DESTINATION]
NetworkFlowOrientor
    DIRECTION_ATTR = _direction
    NETWORK -> FeatureJoiner_2 [RIGHT]
AttributeFilter_3
    ATTR_NAME = missing
    ATTR_VALUES = <Empty>,<Missing>,<Null>,<Unfiltered>,Yes
    <MISSING> -> FeatureJoiner_2 [LEFT]
FeatureJoiner_2
    ATTR_CONFLICT_RES = Prefer Left
    GEOMETRY_HANDLING = Aggregate Left and Right (Enforce Unique Names)
    JOIN_KEYS = json json AUTO
    JOIN_MODE = Full
    JOINED -> AttributeFilter_5
AttributeFilter_5
    ATTR_NAME = missing
    ATTR_VALUES = <Empty>,<Missing>,<Null>,<Unfiltered>,Yes
    <EMPTY> -> GeometryExtractor
    <MISSING> -> GeometryExtractor
    <NULL> -> GeometryExtractor
    <UNFILTERED> -> GeometryExtractor
GeometryExtractor
    ATTR = _geometry
    JSON_MAX_DIGITS = 7
    KIND_LONG = GeoJSON
    REMOVE_GEOMETRY = No
    -> FeatureJoiner_4 [RIGHT]
AttributeFilter_2
    ATTR_NAME = missing
    ATTR_VALUES = <Empty>,<Missing>,<Null>,<Unfiltered>,Yes
    <MISSING> -> SpatialFilter [Candidate]
    Yes -> PolylineAnalyzer
    Yes -> SpatialFilter_2 [Candidate]
PolylineAnalyzer
    ANGLERADIUS = 2.5
    AZIMUTHRADIUS = 2
    LABELPOINTREPLACER_HEIGHT = 1
    OUTPUT_CHOICE = All
    SEGMENTANGLERADIUS = 5
    Segment -> AreaBuilder
    Segment -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> SpatialRelator [Requestor]
AreaBuilder
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> SpatialFilter [Filter]
    AREA -> CenterPointReplacer_2
CenterPointReplacer_2
    POINTTYPE = CENTEROFGRAV
    POINT -> AnchoredSnapper [ANCHOR]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeTrimmer
AttributeTrimmer
    SRC_ATTRS = SketchAlign
    TRIM_CHARS = {"0":["
    TRIM_TO_NONE = Yes
    TRIM_TYPE = Both
    -> AttributeTrimmer_2
AttributeTrimmer_2
    SRC_ATTRS = SketchAlign
    TRIM_CHARS = S"]}
    TRIM_TO_NONE = Yes
    TRIM_TYPE = Both
    -> AttributeFilter_6
AttributeFilter_6
    ATTR_NAME = SketchAlign
    ATTR_VALUES = <Empty>,<Missing>,<Null>,<Unfiltered>
    <UNFILTERED> -> ListBuilder
    <UNFILTERED> -> FeatureJoiner [LEFT]
ListBuilder
    LIST_ATTRS_TO_INCLUDE = SketchAlign
    LIST_NAME = _listof sketchidforroundabout
    -> ListBasedFeatureMerger [REQUESTOR]
ListBasedFeatureMerger
    ATTR_ACCUM_MODE = Merge Supplier
    ATTR_CONFLICT_RES = Use Requestor
    BUILD_INCOMPLETE = Merge Supplier Information
    IGNORE_NULLS = No
    MERGE_TYPE = Attributes Only
    MODE = AUTO
    PROCESS_DUPS = Yes
    REFEEATTR = @Value(id)
    REFERATTR = _listof sketchidforroundabout{}.SketchAlign
    USED_SUPPLIER -> LineOnLineOverlayer [LINE]
LineOnLineOverlayer
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    POINT -> TestFilter
TestFilter
    DEFAULT_VALUE = <UNFILTERED>
    TEST_LIST = "BOOL_OP,OR,COMPOSITE_TEST,""""""1"""""",TEST_CLAUSE,TEST @Value(_overlaps) > 2",@Value(_overlaps) > 2
    <UNFILTERED> -> FeatureJoiner [RIGHT]
FeatureJoiner
    ATTR_CONFLICT_RES = Prefer Right
    GEOMETRY_HANDLING = Prefer Left
    JOIN_KEYS = id id AUTO
    JOIN_MODE = Full
    JOINED -> AnchoredSnapper [CANDIDATE]
AnchoredSnapper
    EXTEND_LINES = NEVER
    SNAPTYPE_PARAM = End Point Snapping
    TOLERANCE = 100
    SNAPPED -> FeatureJoiner_4 [LEFT]
FeatureJoiner_4
    ATTR_CONFLICT_RES = Prefer Right
    GEOMETRY_HANDLING = Prefer Left
    JOIN_KEYS = id id AUTO
    JOIN_MODE = Left
    JOINED -> LineOnLineOverlayer_2 [LINE]
    UNJOINED_RIGHT -> LineOnLineOverlayer_2 [LINE]
LineOnLineOverlayer_2
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    POINT -> SpatialRelator [Supplier]
    LINE -> SpatialFilter_3 [Candidate]
    <REJECTED> -> sf (writer GEOJSON_1)
SpatialRelator
    AGGREGATE_HANDLING = Yes
    CALC_CARD = Yes
    CURVE_BOUNDARY_RULE_PARAM = Default Rule
    LIST_NAME = _relationships
    PREDICATES = INTERSECTS
    SUCCESS_ATTR = _related_suppliers
    -> TestFilter_2
TestFilter_2
    DEFAULT_VALUE = <UNFILTERED>
    TEST_LIST = "BOOL_OP,OR,COMPOSITE_TEST,""""""1"""""",TEST_CLAUSE,TEST @Value(_related_suppliers) > 1",@Value(_related_suppliers) > 1
    <UNFILTERED> -> sf (writer GEOJSON_1)
    @Value(_related_suppliers) > 1 -> SpatialFilter_3 [Filter]
    @Value(_related_suppliers) > 1 -> Extract_End_Points_5 [Input_Features]
Extract_End_Points_5: Extract End Points
    Buffer = 0
    BufferUnit = Feet
    ExtractGeometry = Yes
    Point_Output -> SpatialRelator_2 [Requestor]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialRelator_2 [Supplier]
    PASSED -> AnchoredSnapper_2 [CANDIDATE]
    FAILED -> sf (writer GEOJSON_1)
SpatialRelator_2
    AGGREGATE_HANDLING = Yes
    CALC_CARD = Yes
    CURVE_BOUNDARY_RULE_PARAM = Default Rule
    LIST_NAME = _relationships
    PREDICATES = INTERSECTS
    SUCCESS_ATTR = _related_suppliers
    -> StatisticsCalculator
    -> AnchoredSnapper_3 [CANDIDATE]
StatisticsCalculator
    CALCULATION_MODE = NUMERIC
    FEAT_STATS = _related_suppliers,NUMERIC_MODE,,MAX,,,,,,,,,,,
    COMPLETE -> TestFilter_3
TestFilter_3
    DEFAULT_VALUE = <UNFILTERED>
    TEST_LIST = "BOOL_OP,OR,COMPOSITE_TEST,""""""1"""""",TEST_CLAUSE,TEST @Value(_related_suppliers) = @Value(_related_suppliers.max)",@Value(_related_suppliers) >= @max(@Value(_related_suppliers))
    @Value(_related_suppliers) >= @max(@Value(_related_suppliers)) -> StatisticsCalculator_2
StatisticsCalculator_2
    CALCULATION_MODE = NUMERIC
    FEAT_STATS = _related_suppliers,NUMERIC_MODE,,,COUNT,,,,,,,,,,
    COMPLETE -> AttributeFilter_4
AttributeFilter_4
    ATTR_NAME = _related_suppliers.total_count
    ATTR_VALUES = <Empty>,<Missing>,<Null>,<Unfiltered>,1,2
    1 -> AnchoredSnapper_2 [ANCHOR]
    2 -> LineBuilder
AnchoredSnapper_2
    EXTEND_LINES = NEVER
    SNAPTYPE_PARAM = End Point Snapping
    TOLERANCE = 100
    SNAPPED -> sf (writer GEOJSON_1)
    UNTOUCHED -> sf (writer GEOJSON_1)
LineBuilder
    ACCUM_INPUT_ATTRS = Use Attributes From One Feature
    REMOVE_DUPLICATES = NO
    LINE -> CenterPointReplacer_3
CenterPointReplacer_3
    POINTTYPE = CENTER
    POINT -> AnchoredSnapper_3 [ANCHOR]
AnchoredSnapper_3
    EXTEND_LINES = NEVER
    SNAPTYPE_PARAM = End Point Snapping
    TOLERANCE = 100
    SNAPPED -> sf (writer GEOJSON_1)
    UNTOUCHED -> sf (writer GEOJSON_1)
sf (writer GEOJSON_1)
    attributes: BaseAlign string, SketchAlign string, genType string, properties string, id string, isRoute string, feat_type string, missing string, _direction string, _geometry string, mapType string, geometry string
