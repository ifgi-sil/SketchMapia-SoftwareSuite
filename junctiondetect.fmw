FME workspace junctiondetect.fmw

Parameters:
- data =

Writers:
- TEXTLINE_1: TEXTLINE to output

Note: Creator [Creator] / General: / Geometry Source: Geometry Object / Geometry Object: Null / Coordinate System: <not set> / Number to Create: 1 / Create At End: No / Creation Instance Attribute: _creation_instance
Creator
    GEOMTYPE = Geometry Object
    NUM = 1
    CREATED -> AttributeCreator
Note: AttributeCreator [AttributeCreator] / Attributes To Create: New AttributeAttribute Valuejson$(data)
AttributeCreator
    ATTR_TABLE = SET_TO json = $(data)
    -> Logger
Logger
    LOG_FEATURE = LOG_ONLY
    MAXCOORDS = 20
    MAXFEATS = 20
    MESSAGE = Feature is:
    SEVERITY = INFO
    LOGGED -> JSONFragmenter
Note: JSONFragmenter [JSONFragmenter] / Source: / Input Source: JSON Attribute / JSON Attribute: json / General: / JSON Query: json[*][*] / Fragment as Format: JSON / Reject Features which Produce No Fragments: Yes / Flattening: / Flatten Query Result into Attributes: Yes / Recursively Flatten Objects/Arrays: No / Prefix New Attributes With: <not set> / Attributes to Expose: geometry properties
Note: JSONFragmenter
JSONFragmenter
    EXPLODE_FORMAT = JSON
    EXTRACT_ATTR = Yes
    JSON_ATTR = json
    JSON_QUERY = json[*][*]
    NEW_ATTRIBUTES = geometry properties
    READ_FROM_FILE = NO
    RECURSIVE = No
    REJECT_EMPTY_LISTS = YES
    FRAGMENTS -> JSONFlattener
Note: JSONFlattener [JSONFlattener] / Source: / Input Source: JSON Document / JSON Document: @Value(properties) / Flattening: / Recursively Flatten Objects/Arrays: No / Prefix New Attribute Names With: <not set> / Attributes to Expose: <not set> / Error Handling: / List Attribute for JSON Parsing Errors: _json_error
JSONFlattener
    ERROR_LIST_ATTR = _json_error
    JSON_DOCUMENT = @Value(properties)
    READ_FROM_FILE = NO
    RECURSIVE = No
    -> GeometryReplacer
Note: GeometryReplacer [GeometryReplacer] / General: / Geometry Encoding: GeoJSON / Geometry Source: @Value(geometry) / Remove Attribute: Yes
GeometryReplacer
    ELLIPSOID_NAME = WGS84
    KIND_LONG = GeoJSON
    LETTERING = WGS84
    MSSQL_FORMAT_CHOICE = Geometry
    OGC_WKT_PRECISION_DISPLAY = 64-bit
    OUTPUT_POINT_DISPLAY = Point
    REMOVE_ATTRIBUTE = Yes
    SOURCE = @Value(geometry)
    SRS_AXIS_ORDER_DISPLAY = Automatic
    -> TopologyBuilder
TopologyBuilder
    ALLOW_CYCLES = No
    BOUNDING_EDGES = All
    CLEANING_TOLERANCE = Automatic
    DEAGGREGATE_INPUT = Yes
    GENERATION_MODE = INTERSECT
    MAX = 0
    OVERLAPPING_MODE = No
    LINE -> AttributeJSONPacker
Note: AttributeJSONPacker [AttributeJSONPacker] / [Embedded] / User Parameters: / Filter Prefix (blank for all attributes): <not set> / Packed Attribute Name: _packed / Attributes to Pack: _from_node,_to_node,json
AttributeJSONPacker
    ATTRS = _from_node,_to_node,json
    PACKED = _packed
    -> text_line (writer TEXTLINE_1)
Note: General Parameters: / Writer Type: Text File / Feature Type Name: text_line / Writer: output [TEXTLINE] / Allowed Geometries: All / Exposed Attributes: NameTypetext_line_databuffer
text_line (writer TEXTLINE_1)
    attributes: text_line_data buffer

FME custom transformer AttributeJSONPacker
This transformer packs all the attributes that are chosen, or fit the user filter, into a single attribute, as a dictionary in a JSON compatible format:
{"PRI":"2","COMMENTS":"Test Data"}
This is useful for storing multiple format attributes in a single database field for future conversions back to the original format. 
Binary attributes will be hex-encoded and prefaced with "0x". 
Packed attributes can be unpacked using the AttributeJSONUnpacker transformer.
Input Ports
Input :
Accepts any feature.
Output Ports
Output :
Ouputs the original feature with an added attribute containing the JSON object.
Parameters
Attributes to Pack :
Specific attributes to pack. Chosing any attributes will disable the filter (described below).
Filter Prefix :
All attributes with this prefix will be added to the packed attribute. Leaving this value blank will pack all the attributes.
Packed Attribute Name :
The name of the new attribute containing the packed values

Parameters:
- ATTRS =
- FILTER =
- PACKED =

Input (input)
    -> ParameterFetcher
Note: Get filter value
ParameterFetcher
    ATTR_LIST = AttributeJSONPacker_FILTER {$(FILTER)} AttributeJSONPacker_PACKED {$(PACKED)} AttributeJSONPacker_ATTRS {$(ATTRS)}
    -> PythonCaller
PythonCaller
    NEW_ATTRIBUTES = $(PACKED)
    PYTHONSOURCE:
      from __future__ import absolute_import, division, print_function, unicode_literals

      import fmeobjects
      import binascii
      import json
      import six
      import locale
      import re

      # This class will create a packed list of format
      # attributes suitable for use with @SupplyAttributes()

      def packIgdsAtts(feature):
         # get a list of attribute names
         attlist = feature.getAllAttributeNames()

         # convert the attribute names to Unicode to handle non-ascii characters
         temp_att_list = []
         for att_name in attlist:
             if isinstance(att_name, six.binary_type):
                 temp_att_list.append(six.text_type(att_name, locale.getpreferredencoding()))
             else:
                 temp_att_list.append(att_name)
         attlist = temp_att_list

         # get attributes to pack
         pack_attrs = feature.getAttribute('AttributeJSONPacker_ATTRS').replace('"', '').strip().split(',')

         # get filter value
         filter = feature.getAttribute('AttributeJSONPacker_FILTER')


         # get packed attribute name
         packedAtt = feature.getAttribute('AttributeJSONPacker_PACKED')

         addedAttrs = {
            'AttributeJSONPacker_ATTRS',
            'AttributeJSONPacker_FILTER',
            'AttributeJSONPacker_PACKED',
         }

         # if no filter or packed attribute, then get all attributes
         getAll = False
         if pack_attrs[0] == "" and filter == "":
             getAll = True

         # disable filter if packed attribute chosen
         if pack_attrs[0] != "":
             filter = False

         # create dict for packed attributes
         packed = {}

         # loop through attribute names
         for att in attlist:
             if ((filter and filter in att) or att in pack_attrs or getAll) and att not in addedAttrs:
                 att_value = feature.getAttribute(att)
                 float_val, int_val = None, None
                 # extract numeric types from strings
                 if isinstance(att_value, str):
                     if re.search("[E,e]",att_value) is None:
                         try:
                             float_val = float(att_value)
                             int_val = int(att_value)
                             if int_val == float_val:
                                 att_value = int_val
                             else:
                                 att_value = float_val
                         except ValueError as e:
                             if int_val is not None:
                                 att_value = int_val
                             if (float_val is not None) and (float_val != float("inf")) and (float_val != float("-inf"))and (float_val != float("nan")):
                                 att_value = float_val

                 # convert binary attributes to hex for storage
                 if type(att_value) == bytearray:
                     att_value = "0x" + binascii.hexlify(att_value)
                 # append attribute value
                 packed[att] = att_value

         #add packed attributes in JSON format
         if six.PY2:
             packedAttJson = json.dumps(packed,separators=(',', ':'), ensure_ascii=False, encoding=locale.getpreferredencoding())
         else:
             packedAttJson = json.dumps(packed,separators=(',', ':'), ensure_ascii=False)
         feature.setAttribute(packedAtt,packedAttJson)
    PYTHONSYMBOL = packIgdsAtts
    -> Output (output)
Output (output)
